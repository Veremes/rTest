FME workspace scenarioPlayer.fmw
Title: scenarioPlayer
Description: Exécute les traitements et vérifications contenus dans un fichier scénario au format xml/rTest puis génère un rapport au format html (en fait GML + feuille de style XSL).
La vérification est sous-traitée par des appels à checkerXML.fmw
scenarioPlayer est le projet maître de l'outil de test de régression rTest conçu et développé par Veremes (http://www.veremes.com) - 2016.
Usage: Paramètres :
scenarioXml : emplacement et nom du fichier scenario à lire et exécuter
destHtml : emplacement et nom du rapport html résultat
History: 01/05/2016,O.Gayte - Veremes,Première publication libre, externe à Veremes,01/06/2017,O.Gayte - Veremes,For FME2017 UC Conf Vancouver,11/06/2017,O.Gayte + Bo Guo,Support for Unix Path

Parameters:
- scenarioXml = $(FME_MF_DIR)scenario\sc_HelloWorld.xml   # Scenario file (.xml) 
- destHtml = $(FME_MF_DIR)report\world.html   # HTML Report file 
- destSqlite:   # Python Script
      import os
      destSqlite=FME_MacroValues['FME_MF_DIR'] + 'result/rTest.sqlite'
      if os.path.exists(destSqlite):
          try:
              os.remove(destSqlite)
          except:
              print 'Impossible de supprimer : ' + destSqlite
      return destSqlite
- destGmlFile:   # Script Python
      import uuid
          #return FME_MacroValues['FME_MF_DIR'] + 'result/' + str(uuid.uuid4()) + '.gml'
      return FME_MacroValues['FME_MF_DIR'] + 'result/' + 'gml.gml'
- logDir:   # Python Script
      import os
      logDir=FME_MacroValues['FME_MF_DIR'] + 'log/'
      if not os.path.exists(logDir):
          try:
              os.mkdir(logDir)
          except:
              print 'Unable to create log directoy: ' + logDir
      return logDir
- destReportDir:   # Python Script
      import os
      destReportDir=os.path.dirname(FME_MacroValues['destHtml'])
      destReportDir =  destReportDir.replace('(FME_MF_DIR)', FME_MacroValues['FME_MF_DIR'])
      destReportDir =  destReportDir.replace('$', '')
      if not os.path.exists(destReportDir):
          try:
              os.mkdir(destReportDir)
          except:
              print 'Unable to create report directoy: ' + destReportDir
      return destReportDir

Readers:
- XML_1: XML from $(scenarioXml)

Writers:
- GML_1: GML to $(destGmlFile)

Note: If the check fails / the process must fail with error
Terminator
    MESSAGE:
      Traitement interrompu suite à une erreur d'exécution d'un traitement de vérification (checker).
      Consultez le log de checkerXML.fmx dans : $(FME_MF_DIR_USERTYPED)/checkerXML.log
Note: Rebuild each RTest with a list / of processes and a list of checks
FeatureMerger_2
    ATTR_CONFLICT_RES = Use Requestor
    SUPPLIERS_FIRST = No
    PROCESS_DUPS = No
    ATTR_ACCUM_MODE = Merge Supplier
    MERGE_TYPE = Attributes Only
    IGNORE_NULLS = No
    JOIN_KEYS = @Value(rt.name) @Value(rtest) AUTO
    MERGED -> Sorter
Note: Sort the result. / Probably useless...
Sorter
    SORT_PARM = rt.count NUMERIC ASCENDING
    SORTED -> AttributeRemover_2
Note: Clean
AttributeRemover_2
    LIST_ATTRS = checkCollection.check{}.rtest
    REMOVE_ATTRS = rtest,rt.count
    -> AttributeRenamer_3
AttributeRenamer_3
    ATTR_LIST = rt.name,name,
    -> rtest (writer GML_1)
Note: Write the GML file / + transform the GML into HTML / by applying the xslt stylesheet / + delete the gml file
rtest (writer GML_1)
    attributes: name xml_char(200), processCollection.process{}.rt.name xml_char(200), processCollection.process{}.rt.count xml_char(200), processCollection.process{}.workspace xml_char(200), processCollection.process{}.parameters xml_char(200), processCollection.process{}.description xml_char(200), processCollection.process{}.log xml_char(200), processCollection.process{}.process xml_char(200), processCollection.process{}.duration xml_char(200), processCollection.process{}.currentprocessmemory xml_char(200), processCollection.process{}.peakmemory xml_char(200), processCollection.process{}.status xml_char(200), checkCollection.check{}.description xml_char(200), checkCollection.check{}.return xml_char(200), checkCollection.check{}.success xml_boolean, checkCollection.check{}.date xml_char(200), checkCollection.check{}.expected xml_char(200)

Bookmark: Read the XML Scenario file
scenario (reader XML_1)
    attributes: sc.author xml_char(7), sc.description xml_char(17), sc.name xml_char(14), sc.scenario.monnom xml_char(14), xml_fragment xml_xml, xml_id xml_char(14), xml_matched_element xml_char(9), xml_parent_child_pos xml_char(1), xml_parent_id xml_char(1), sc.fme_path xml_char(100)
    -> XMLFormatter
XMLFormatter
    XML_INPUT_TYPE = Attribute Specifying XML Text
    XML_OUTPUT_ATTR = xml_fragment
    REMOVE_EMPTY_ELEMENT = No
    XML_ATTR_TEXT = xml_fragment
    OUTPUT_ENCODING = utf-8
    WHITESPACE_HANDLING = Remove excess whitespace
    XML_OUTPUT_TYPE = Attribute
    NAMESPACE_CLEANUP = No
    FORMATTING_CHOICE = Linearize XML
    LIST_NAME = _xml_error
    COLLAPSE_EMPTY_ELEMENT = No
    SCHEMALOC_CLEANUP = No
    REMOVE_ALL_COMMENT = No
    PASSED -> XMLFragmenter
Note: Extract rtest Elements
XMLFragmenter
    MERGE_ATTRS = Yes
    XML_SOURCE_TYPE = Attribute with XML document
    ATTRIBUTE_XML = xml_fragment
    EMBEDDED_EXPRESSIONS = rtestCollection/rtest
    FLATTEN_OPTIONS = <structure separator="." map-empty-elements="yes" matched-prefix="attributes" matched-attributes="yes" cardinality="+{?}" structure-prefix="rt." child-position-attribute="" except-expression="checkCollection" ui-mode="basic" matched-ancestor-attributes="grandparent parent root"/>
    NEW_ATTRIBUTES = rt.name rt.enabled rt.deletebefore
    FEATURE_TYPES_FORMAT_NAME = XML
    FRAGMENTS -> Counter
Note: For synchronization
Counter
    CNT_ATTR = rt.count
    DOMAIN = counter
    SCOPE = Global
    START = 0
    -> Tester
Note: is the rtest enabled?
Tester
    BOOL_OP = OR
    TEST_MODE = Automatic
    TEST_DESCRIPTION = ""
    TEST_CLAUSE = TEST @Value(rt.enabled) = true
    PASSED -> OrderedCloner
OrderedCloner
    First -> PythonCaller_3
    Second -> XMLFragmenter_4
Note: delete file into the element / "deleteBefore"
PythonCaller_3
    PYTHONSOURCE:
      # coding: ISO-8859-2
      import fme
      import fmeobjects
      import os

      def deleteBefore(feature):
          filestodelete=os.sep.join(os.sep.join(feature.getAttribute("rt.deletebefore").split('/')).split('\\'))
          from glob import glob
          try:
              for filename in glob(filestodelete):
                  os.remove(filename)
                  #print("deleteBefore:"+filename)
          except:
              pass
    PYTHONSYMBOL = deleteBefore
    NEW_ATTRIBUTES = fmeProcessStatus parameters log process
    -> XMLFragmenter_3
Note: Extract checker elements
XMLFragmenter_4
    MERGE_ATTRS = Yes
    XML_SOURCE_TYPE = Attribute with XML document
    ATTRIBUTE_XML = xml_fragment
    EMBEDDED_EXPRESSIONS = checkCollection/check
    FLATTEN_OPTIONS = <structure separator="." map-empty-elements="yes" matched-prefix="attributes" matched-attributes="yes" cardinality="+{?}" structure-prefix="ch." child-position-attribute="" except-expression="" ui-mode="basic" matched-ancestor-attributes="parent"/>
    NEW_ATTRIBUTES = ch.description ch.condition.type ch.condition.value ch.source.format ch.source.dataset ch.source.type ch.source.connection
    FEATURE_TYPES_FORMAT_NAME = XML
    FRAGMENTS -> FeatureCounter
    FRAGMENTS -> AttributeRenamer_4

Bookmark: Run the FME workspace
Note: Extract process / elements
XMLFragmenter_3
    MERGE_ATTRS = Yes
    XML_SOURCE_TYPE = Attribute with XML document
    ATTRIBUTE_XML = xml_fragment
    EMBEDDED_EXPRESSIONS = process
    FLATTEN_OPTIONS = <structure separator="." map-empty-elements="yes" matched-prefix="attributes" matched-attributes="yes" cardinality="+{?}" structure-prefix="pr." child-position-attribute="" except-expression="" ui-mode="basic" matched-ancestor-attributes=""/>
    NEW_ATTRIBUTES = pr.workspace pr.description pr.logfile
    FEATURE_TYPES_FORMAT_NAME = XML
    FRAGMENTS -> PythonCaller_2
Note: run fme process
PythonCaller_2
    PYTHONSOURCE:
      # coding: ISO-8859-2
      import fme
      import fmeobjects
      import string
      import subprocess, sys
      import uuid
      import os.path
      import platform

      def processFeature_pc2(feature):
          logger = fmeobjects.FMELogFile()
          reload(sys)
          sys.setdefaultencoding("ISO-8859-2")
          listArgs=[]
          logfile=feature.getAttribute("pr.logfile")
          if logfile==None:
              logfile=''

          fme_path=feature.getAttribute("sc.fme_path")
          workspace=feature.getAttribute("pr.workspace")
          #checks if fme_path and workspace exists
          if (fme_path.lower() != 'fme.exe') and (not os.path.isfile(fme_path)):
              #if not os.path.isfile(fme_path):
              logger.logMessageString("The FME path doesn't exist : " + fme_path)
              raise Exception("Invalid fme_path")
          workspace = os.sep.join(os.sep.join(workspace.split('/')).split('\\'))
          logger.logMessageString(workspace)
          if not os.path.isfile(workspace):
              logger.logMessageString("The workspace file doesn't exist : " + workspace)
              raise Exception("Invalid Workspace file")

          listArgs.append(fme_path)
          listArgs.append(workspace)
          listeParams=feature.getAttribute("pr.parameterCollection.parameter{}.name")
          listeValue=feature.getAttribute("pr.parameterCollection.parameter{}.value")

          # Manage 3 differents cases : no parameter, only one and several
          if (listeParams==None):
              params=feature.getAttribute("pr.parameterCollection.parameter.name")
              if (params!=None):
                  value=feature.getAttribute("pr.parameterCollection.parameter.value")
                  listArgs.append(u"--" + params)
                  listArgs.append(value)
          else:
              for i in range(0,len(listeParams)):
                  parameterName = feature.getAttribute("pr.parameterCollection.parameter{"+str(i)+"}.name")
                  listArgs.append(u"--" + feature.getAttribute("pr.parameterCollection.parameter{"+str(i)+"}.name"))
                  value = feature.getAttribute("pr.parameterCollection.parameter{"+str(i)+"}.value")
                  listArgs.append(value)
          listArgs.append(u"-LOG_FILENAME")
          if logfile=='':
              logfile = FME_MacroValues['logDir']+str(uuid.uuid4())+'.log'
          listArgs.append(logfile)
          logger.logMessageString("listArgs:"+str(listArgs))
          fmeProcess = subprocess.Popen(listArgs,stdout=None,stderr=None)
          feature.setAttribute("process",os.path.basename(workspace))
          feature.setAttribute("log",logfile)
          feature.setAttribute("parameters",str(listArgs))
          feature.setAttribute("fmeProcessStatus",fmeProcess.wait())
    PYTHONSYMBOL = processFeature_pc2
    NEW_ATTRIBUTES = fmeProcessStatus parameters log process
    -> PythonCaller_4
Note: log analysis
PythonCaller_4
    PYTHONSOURCE:
      # coding: utf8
      import fmeobjects
      import re

      # Template Function interface:
      def processFeature_pc4(feature):
          logfile=feature.getAttribute("log")
          try:
              oFile=open(logfile,'r')
              #une boucle correspondant au nombre de ligne
              for line in oFile:
                  # on effectue la reche dans la ligne
                  match = re.search(r'FME Session Duration: (.*). \(',str(line))
                  if match:
                      duration=match.group(1)
                      #print duration
                      feature.setAttribute("duration",duration)

                  match = re.search(r'END (.*)peak process memory usage: (.*), current process memory usage: (.*)',str(line))
                  if match:
                      peakmemory=match.group(2)
                      currentprocessmemory=match.group(3)
                      feature.setAttribute("peakmemory",peakmemory)
                      feature.setAttribute("currentprocessmemory",currentprocessmemory)
                      #print peakmemory
                      #print currentprocessmemory
              oFile.close()
          except:
              pass
    PYTHONSYMBOL = processFeature_pc4
    NEW_ATTRIBUTES = duration currentprocessmemory peakmemory
    -> AttributeCreator
Note: Set the status
AttributeCreator
    ATTR_LIST = status,"FME_CONDITIONAL:DEFAULT_VALUE'Failed'BOOL_OP;OR;COMPOSITE_TEST;<Unused>;TEST @Value(fmeProcessStatus) = 0'Success'FME_NUM_CONDITIONS2___"
    -> AttributeRenamer_2
Note: rename before / writing the result
AttributeRenamer_2
    ATTR_LIST = pr.description,description,,pr.workspace,workspace,,rt.processCollection.process.parameterCollection.parameter,parameters,
    -> AttributeKeeper_2
Note: cleaning
AttributeKeeper_2
    KEEP_ATTRS = currentprocessmemory,description,duration,log,parameters,peakmemory,process,rt.count,status,workspace,rt.name
    -> ListBuilder
Note: Create a list of process / for each rTest / processCollection.process
ListBuilder
    GRP_BY = rt.count rt.name
    LIST_NAME = processCollection.process
    -> FeatureMerger_2 [REQUESTOR]

Bookmark: Launch the checking actions
AttributeRenamer_4
    ATTR_LIST = xml_fragment,xml_check,
    -> Counter_2
Note: Number the checks
Counter_2
    CNT_ATTR = _checkNumber
    DOMAIN = counter
    SCOPE = Global
    START = 1
    -> XMLFormatter_2
XMLFormatter_2
    XML_INPUT_TYPE = Attribute Specifying XML Text
    XML_OUTPUT_ATTR = xml_check
    REMOVE_EMPTY_ELEMENT = No
    XML_ATTR_TEXT = xml_check
    OUTPUT_ENCODING = utf-8
    WHITESPACE_HANDLING = Remove excess whitespace
    XML_OUTPUT_TYPE = Attribute
    NAMESPACE_CLEANUP = No
    FORMATTING_CHOICE = Linearize XML
    LIST_NAME = _xml_error
    COLLAPSE_EMPTY_ELEMENT = No
    SCHEMALOC_CLEANUP = No
    REMOVE_ALL_COMMENT = No
    PASSED -> StringPairReplacer
Note: WorkspaceRunner don't / like some strings...
StringPairReplacer
    MAP = , <coma> ' '
    SRC_ATTR = xml_check
    CASE = no
    RESULT_ATTR = xml_check
    -> WorkspaceRunner
Note: Checks are subcontracted to / checkerXML.fmw
WorkspaceRunner
    BLOCKING = Yes
    WORKSPACE_FILE = $(FME_MF_DIR)checkerXML.fmw
    WORKSPACE_PARAMETERS = rtest,@Value(rt.name),checker,@Value(xml_check),dbConnection,@Value(ch.source.connection),destSqlite,$(destSqlite)
    SUCCEEDED -> FeatureMerger [SUPPLIER]
    FAILED -> Terminator

Bookmark: Synchronisation
Note: Number the checks
Note: We want to know when the checks are done / before to read the file / 'result/test.sqlite' and generate the report
FeatureCounter
    -> AttributeKeeper
AttributeKeeper
    KEEP_ATTRS = _number
    -> FeatureMerger [REQUESTOR]
FeatureMerger
    ATTR_CONFLICT_RES = Use Requestor
    SUPPLIERS_FIRST = No
    PROCESS_DUPS = No
    ATTR_ACCUM_MODE = Merge Supplier
    MERGE_TYPE = Attributes Only
    IGNORE_NULLS = No
    JOIN_KEYS = @Value(_number) @Value(_checkNumber) AUTO
    MERGED -> ParameterFetcher
    MERGED -> FeatureReader [INITIATOR]

Bookmark: Write the Control element for the destination GML file
ParameterFetcher
    ATTR_LIST = dataset {$(scenarioXml)}
    -> TimeStamper
TimeStamper
    TIME_ATTR = date
    FMT = ^Y/^m/^d ^H:^M:^S
    -> AttributeRenamer
AttributeRenamer
    ATTR_LIST = sc.description,description,,sc.author,author,,sc.name,scenario,,sc.fme_path,fme_path,
    -> control (writer GML_1)
control (writer GML_1)
    attributes: scenario xml_char(200), description xml_buffer, dataset xml_char(200), date xml_date, author xml_char(200), fme_path xml_char(200)

Bookmark: Reporting
Note: Read the Sqlite database / containing the check results.
FeatureReader
    SQLITE3_QUERY_FEATURE_TYPES_FOR_MERGE_FILTERS = Yes
    FORMAT = SQLITE3
    DATASET = $(destSqlite)
    ATTRIBUTES = test,"description,return,success,date,rtest"
    OUTPUT_FEATURES_DISPLAY = Based on Connections
    FEATURETYPES_RADIO = FEATURETYPES
    ATTR_ACCUM_MODE = Only Use Result
    FEATURETYPES = test
    COMBINE_GEOM = Use Result
    test -> AttributeExposer
AttributeExposer
    ATTR_LIST = expected
    -> ListBuilder_2
Note: Create a list of check for each rTest / processCollection.process / checkCollection.check
ListBuilder_2
    GRP_BY = rtest
    LIST_NAME = checkCollection.check
    -> FeatureMerger_2 [SUPPLIER]

FME custom transformer FeatureCounter
Compte les entités passant dans le transformer. 
1 seule entité ressort avec un attribut _number

Input (input)
    -> PythonCaller
PythonCaller
    PYTHONSOURCE:
      import pyfme

      class FeatureCounter(object):
           def __init__(self):
               self.logger = pyfme.FMELogfile()
               #self.logger.log('initilisation de FeatureCounter : 1 fois ... ',1)
               self.count = 0
               self.feature = None

           def input(self,feature):
               self.count +=1
               self.feature = feature

           def close(self):
               #self.logger.log('close de FeatureCounter : 1 fois ... ',1)
               if self.feature != None:
                  self.feature.setAttribute('_number',self.count)
                  self.pyoutput(self.feature)
    PYTHONSYMBOL = FeatureCounter
    NEW_ATTRIBUTES = _number
    -> Output (output)
Output (output)
PythonCaller_2
    PYTHONSOURCE:
      import pyfme

      class FeatureCounter(object):
           def __init__(self):
               self.logger = pyfme.FMELogfile()
               #self.logger.log('initilisation de FeatureCounter : 1 fois ... ',1)
               self.count = {}
               self.feature={}

           def input(self,feature):
               attributeValue = feature.getAttribute('valeurAttribut')
               attributeId = feature.getAttribute('id_attribute')
               if not self.count.has_key(attributeId):
                      #self.logger.log('initialisation ' + str(attributeId),1)
                      self.count[attributeId]=1
               else:
                   self.count[attributeId] +=1
               self.feature[attributeId]=feature

           def close(self):
               #self.logger.log('close de FeatureCounter : 1 fois ... ',1)
               for attributeId in self.count:
                   self.feature[attributeId].setAttribute('_number',self.count[attributeId])
                   self.pyoutput(self.feature[attributeId])
    PYTHONSYMBOL = FeatureCounter
    NEW_ATTRIBUTES = _number

FME custom transformer OrderedCloner

Input (input)
    -> Cloner
Cloner
    COPIES = 2
    COPYATT = __copynum
    COPY -> AttributeFilter
AttributeFilter
    ATTR_VALUES = <EMPTY>,<MISSING>,<NULL>,<UNFILTERED>,0,1
    ATTR_NAME = __copynum
    0 -> AttributeRemover
    1 -> AttributeRemover_2
AttributeRemover
    REMOVE_ATTRS = __copynum
    -> First (output)
First (output)
AttributeRemover_2
    REMOVE_ATTRS = __copynum
    -> Second (output)
Second (output)
