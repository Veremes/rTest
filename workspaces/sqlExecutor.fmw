FME workspace sqlExecutor.fmw

Parameters:
- dbConnection = olivier@localhost:5430/qualigeo   # Connexion nommée 
- dbFormat = POSTGRES   # Spatial Object,ORACLE8I Format Base de données 
- sql = select error_number as return from q_control.control where id_control = 200   # Requête 

Creator
    NUM = 1
    GEOMTYPE = Geometry Object
    CREATED -> ParameterFetcher_2
Note: Impossible d'utiliser operator / sous forme de paramètre publié. / bug de fme 2015 ?
ParameterFetcher_2
    ATTR_LIST = _sql {$(sql)}
    -> StringPairReplacer
Note: Gestion des / caractères spéciaux
StringPairReplacer
    SRC_ATTR = _sql
    CASE = no
    RESULT_ATTR = _sql
    MAP = <coma> , ' '
    -> SQLExecutor
SQLExecutor
    DATASET = $(dbConnection)
    POSTGRES_QUERY_FEATURE_TYPES_FOR_MERGE_FILTERS = Yes
    SQL_STATEMENT = @Value(_sql)
    COMBINE_ATTRS = Keep Initiator Attributes if Conflict
    EXPOSED_ATTRIBUTE_LIST = return
    FORMAT = POSTGRES
    POSTGRES_NAMED_CONNECTION = $(dbConnection)
    COMBINE_GEOM = Initiator Geometry Only
    RESULT -> SQLExecutor_Result
SQLExecutor_Result: Logger
    MAXCOORDS = 20
    MAXFEATS = 20
    MESSAGE = Feature is:
