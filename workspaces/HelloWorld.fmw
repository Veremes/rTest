FME workspace HelloWorld.fmw

Parameters:
- xy = 22.0 -29.0   # Long-Lat Point Coordinates (space delimited)

Readers:
- SHAPE_1: SHAPE from $(FME_MF_DIR)data\TM_WORLD_BORDERS_SIMPL-0.3.zip

Writers:
- SPATIALITE_1: SPATIALITE to $(FME_MF_DIR)result\country.sqlite

Note: Read the input point / in published parameter
Creator
    NUM = 1
    COORDS = $(xy)
    GEOMTYPE = 2D Coordinate List
    CREATED -> SpatialFilter [input 1]
Note: World DataSource SHP
TM_WORLD_BORDERS_SIMPL-0.3 (reader SHAPE_1)
    attributes: FIPS char(2), ISO2 char(2), ISO3 char(3), UN number(3,0), NAME char(50), AREA number(7,0), POP2005 number(10,0), REGION number(3,0), SUBREGION number(3,0), LON number(8,3), LAT number(7,3)
    -> SpatialFilter [input 2]
Note: Let pass the country / that contains input point
SpatialFilter
    USE_BOUNDING_BOX = No
    MERGE_ATTRS = Yes
    BASE_TYPE = Multiple Filters
    PASS_CRITERIA = Pass Against One Filter
    PREDATTR = _predicate
    PREDICATES = WITHIN
    CURVE_BOUNDARY_RULE_PARAM = Default Rule
    PASSED -> country (writer SPATIALITE_1)
Note: Spatialite
country (writer SPATIALITE_1)
    attributes: name string(50), pop2005 real(31,15), region real(31,15), subregion real(31,15)
